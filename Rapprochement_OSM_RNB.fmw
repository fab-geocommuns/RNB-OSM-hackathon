FME workspace Rapprochement_OSM_RNB.fmw

Parameters:
- SourceDataset_GEOJSON = $(FME_MF_DIR)limites_communales_metro_epsg4326.geojson   # Source GeoJSON File or URL
- SourceDataset_GEOJSON_5 = $(FME_MF_DIR)RNB_nat_shape_only.geojson   # Source GeoJSON File or URL
- SourceDataset_GEOJSON_4 = $(FME_MF_DIR)export.geojson   # Source GeoJSON File or URL
- DestDataset_OGCGEOPACKAGE = $(FME_MF_DIR)resultat-1.gpkg   # GeoPackage File
- DestDataset_GEOJSON_2 = $(FME_MF_DIR)RNB-SMH.json   # Destination GeoJSON File
- DestDataset_GEOJSON = $(FME_MF_DIR)OSM-RNB-SMH.json   # Destination GeoJSON File

Readers:
- GEOJSON_1: GEOJSON from $(SourceDataset_GEOJSON) in EPSG:4326
- GEOJSON_2: GEOJSON from $(SourceDataset_GEOJSON_5) in EPSG:4326
- GEOJSON_3: GEOJSON from $(SourceDataset_GEOJSON_4) in EPSG:4326

Writers:
- OGCGEOPACKAGE_1: OGCGEOPACKAGE to $(DestDataset_OGCGEOPACKAGE) in EPSG:4326
- GEOJSON_4: GEOJSON to $(DestDataset_GEOJSON) in EPSG:4326
- GEOJSON_5: GEOJSON to $(DestDataset_GEOJSON_2) in EPSG:4326

RNB_nat_shape_only (reader GEOJSON_2)
    attributes: rnb_id string, status string, addresses{} string
    -> Clipper [CANDIDATE]
GeometryFilter
    FILTER_MODE = SIMPLE
    FILTER_MULTI = FILTER_TYPES]"Surface Area"]FME_CONTROLLER_QUERY_FILE]]FME_CONTROLLER_CHOICE]Simple
    Area -> Clipper_2 [CLIPPER]
    Area -> RNB (writer OGCGEOPACKAGE_1)
    Area -> Batiment RNB (writer GEOJSON_5)
    Area -> AreaCalculator_3
RNB (writer OGCGEOPACKAGE_1)
    attributes: rnb_id text, status text, addresses{} text, _clipped text(3)
Batiment RNB (writer GEOJSON_5)
    attributes: rnb_id string, status string, addresses{} string, _clipped string
export (reader GEOJSON_3)
    attributes: id string, @id string, building string, building:levels string, roof:shape string, type string, addr:city string, addr:country string, addr:housename string, addr:housenumber string, addr:postcode string, addr:street string, amenity string, contact:website string, name string, alt_name string, old_name string, operator string, roof:levels string, source string, short_name string, url string, wikidata string, website string, note string, building:colour string, demolished:building string, building:material string, description string, roof:colour string,
      wikipedia string, wheelchair string, faculty string, official_name string, ref:UAI string, building:flats string, building:levels:underground string, building:prefabricated string, start_date string, email string, height string, roof:direction string, roof:height string, source:height string, check_date string, phone string, wikimedia_commons string, internet_access string, opening_hours string, shop string, toilets string, branch string, brand string, brand:wikidata string, brand:wikipedia string, layer string, survey:date string, loc_name string, leisure string, sport string,
      denomination string, ref:FR:CEF string, religion string, school:FR string, operator:wikidata string, operator:wikipedia string, air_conditioning string, check_date:opening_hours string, clothes string, second_hand string, disused:shop string, @relations{}.role string, @relations{}.rel int, @relations{}.reltags.building string, @relations{}.reltags.name string, @relations{}.reltags.operator string, @relations{}.reltags.type string, outdoor_seating string, payment:credit_cards string, payment:debit_cards string, image string, location string, power string, substation string, fee string, tourism string, atm string, bic string, change_machine string, copy_facility string,
      ref:FR:LaPoste string, stamping_machine string, nohousenumber string, ref:FR:CNC string, screen string, bulk_purchase string, contact:facebook string, contact:phone string, organic string, disused:amenity string, roof:orientation string, smoking string, deaf:description:fr string, contact:email string, disused:leisure string, heritage string, heritage:operator string, historic string, mhs:inscription_date string, ref:mhs string, source:heritage string, contact:city string, contact:housenumber string, contact:postcode string, contact:street string, craft string, building:material:concrete string, community_centre string, community_centre:for string, opening_hours:signed string,
      artist_name string, artwork_type string, ref:FR:SIRET string, operator:type string, ref:FR:gdo string, utility string, voltage string, microbrewery string, disused:historic string, access string, bicycle_parking string, capacity string, covered string, police:FR string, fax string, healthcare string, website:menu string, ref string, transformer string, beds string, ref:FR:FINESS string, ref:FR:NAF string, social_facility string, social_facility:for string, type:FR:FINESS string, service:bicycle:ebike string, service:bicycle:repair string, service:bicycle:retail string, brewery string, charge string,
      min_age string, payment:cash string, drink:beer string, drink:wine string, bakehouse string, oven string, cuisine string, diet:vegetarian string, drive_through string, indoor_seating string, internet_access:fee string, takeaway string, dispensing string, service string, facebook string, origin string, delivery string, access:covid19 string, delivery:covid19 string, drive_through:covid19 string, takeaway:covid19 string, office string, @relations{}.reltags.addr:city string, @relations{}.reltags.addr:housenumber string, @relations{}.reltags.addr:postcode string, @relations{}.reltags.addr:street string, @relations{}.reltags.building:levels string, traffic_signals string, building:min_level string, trade string,
      brand:website string, telecom string, bench string, lit string, mapillary string, network string, passenger_information_display string, shelter_type string, service:vehicle:tyres string, automated string, self_service string, check_date:diet:halal string, diet:halal string, man_made string, kindergarten:FR string, contact:instagram string, healthcare:speciality string, fast_food string, stars string, building:part string, contact:linkedin string, instagram string, toilets:wheelchair string, parking string, surface string, architect string, diet:meat string, diet:vegan string, green_roof string, monitoring:air_quality string,
      government string, fixme string, disused:craft string, ref:FR:Paul:id string, service:bicycle:second_hand string, conveying string
    -> AttributeKeeper
AttributeKeeper
    CREATE_BULK_MODE_FEATURES = NO
    KEEP_ATTRS = id
    -> AreaCalculator
    -> Clipper_3 [CLIPPER]
    -> FeatureJoiner [RIGHT]
Table1 (writer OGCGEOPACKAGE_1)
    attributes: id text, area_osm double, pourcentage double, rnb_id text, status text, area_osm_recouv double
FeatureJoiner_2
    ATTR_CONFLICT_RES = Prefer Left
    GEOMETRY_HANDLING = Prefer Left
    JOIN_KEYS = id id AUTO rnb_id rnb_id AUTO
    JOIN_MODE = Inner
    JOINED -> FeatureJoiner [LEFT]
    UNJOINED_LEFT -> FeatureJoiner [LEFT]
    UNJOINED_RIGHT -> FeatureJoiner [LEFT]
Correspondance OSM - RNB (writer GEOJSON_4)
    attributes: id string, note string, rnb_id string, diff string

Bookmark: Filtre sur SMH
limites_communales_metro_epsg4326 (reader GEOJSON_1)
    attributes: code_insee int, nom string, trigram string, code_postal int, geo_shape string, geo_point_2d{} float
    -> Tester
Tester
    BOOL_OP = OR
    TEST_CLAUSE = TEST @Value(code_insee) = 38421
    TEST_MODE = TEST
    PASSED -> Clipper [CLIPPER]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> GeometryFilter

Bookmark: On calcule la surface de recouvrement d'un objet RNB par OSM
AreaCalculator_3
    AREA_ATTR = area_rnb
    AREA_TYPE = Plane Area
    MULT = 1
    -> Clipper_3 [CANDIDATE]
Clipper_3
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AreaCalculator_4
AreaCalculator_4
    AREA_ATTR = area_rnb_recouv
    AREA_TYPE = Plane Area
    MULT = 1
    -> AttributeManager_4
AttributeManager_4
    ATTR_TABLE = SET_TO pourcentage = @round(@div(@mult(@Value(area_rnb_recouv),100),@Value(area_rnb)),0)
    -> Tester_5

Bookmark: On calcule la surface de recouvrement d'un objet OSM par le RNB
AreaCalculator
    AREA_ATTR = area_osm
    AREA_TYPE = Plane Area
    MULT = 1
    -> Clipper_2 [CANDIDATE]
Clipper_2
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AreaCalculator_2
AreaCalculator_2
    AREA_ATTR = area_osm_recouv
    AREA_TYPE = Plane Area
    MULT = 1
    -> AttributeManager
AttributeManager
    ATTR_TABLE = SET_TO pourcentage = @round(@div(@mult(@Value(area_osm_recouv),100),@Value(area_osm)),0)
    -> Table1 (writer OGCGEOPACKAGE_1)
    -> Tester_2

Bookmark: On filtre sur 70 et on calcule la reodndance Id_OSM et Id_RNB
Tester_2
    BOOL_OP = OR
    TEST_CLAUSE = TEST @Value(pourcentage) < 70
    TEST_MODE = TEST
    FAILED -> StatisticsCalculator
StatisticsCalculator
    CALCULATION_MODE = NUMERIC
    FEAT_STATS = rnb_id,NUMERIC_MODE,,,COUNT,,,,,,,,,,
    GROUP_BY = rnb_id
    COMPLETE -> StatisticsCalculator_2
StatisticsCalculator_2
    CALCULATION_MODE = NUMERIC
    FEAT_STATS = id,NUMERIC_MODE,,,COUNT,,,,,,,,,,
    GROUP_BY = id
    COMPLETE -> Tester_3

Bookmark: 1 RNB pour 1 OSM
Tester_3
    BOOL_OP = COMPOSITE
    COMPOSITE_TEST = 1 AND 2
    TEST_CLAUSE:
      TEST @Value(rnb_id.total_count) = 1
      TEST @Value(id.total_count) = 1
    TEST_MODE = TEST
    PASSED -> AttributeManager_2
    FAILED -> Tester_4
AttributeManager_2
    ATTR_TABLE:
      RENAME_SET_VALUE pourcentage > note = @Value(note)/100
      SET_TO diff
      REMOVE area_osm
      REMOVE _clipped
      REMOVE status
      REMOVE addresses{}
      REMOVE area_osm_recouv
      REMOVE rnb_id.total_count
      REMOVE id.total_count
    -> FeatureJoiner_2 [LEFT]

Bookmark: 1RNB pour X OSM
Tester_4
    BOOL_OP = OR
    TEST_CLAUSE = TEST @Value(id.total_count) = 1
    TEST_MODE = TEST
    PASSED -> AttributeManager_3
AttributeManager_3
    ATTR_TABLE:
      RENAME_SET_VALUE pourcentage > note = @Value(note)/100
      SET_TO diff = splitted
      REMOVE area_osm
      REMOVE _clipped
      REMOVE status
      REMOVE addresses{}
      REMOVE area_osm_recouv
      REMOVE rnb_id.total_count
      REMOVE id.total_count
    -> FeatureJoiner [LEFT]

Bookmark: On filtre sur 70 et on calcule la reodndance Id_OSM et Id_RNB
Tester_5
    BOOL_OP = OR
    TEST_CLAUSE = TEST @Value(pourcentage) < 70
    TEST_MODE = TEST
    FAILED -> StatisticsCalculator_3
StatisticsCalculator_3
    CALCULATION_MODE = NUMERIC
    FEAT_STATS = rnb_id,NUMERIC_MODE,,,COUNT,,,,,,,,,,
    GROUP_BY = rnb_id
    COMPLETE -> StatisticsCalculator_4
StatisticsCalculator_4
    CALCULATION_MODE = NUMERIC
    FEAT_STATS = id,NUMERIC_MODE,,,COUNT,,,,,,,,,,
    GROUP_BY = id
    COMPLETE -> Tester_6

Bookmark: 1 OSM pour 1 RNB
Tester_6
    BOOL_OP = COMPOSITE
    COMPOSITE_TEST = 1 AND 2
    TEST_CLAUSE:
      TEST @Value(rnb_id.total_count) = 1
      TEST @Value(id.total_count) = 1
    TEST_MODE = TEST
    PASSED -> AttributeManager_5
    FAILED -> Tester_7
AttributeManager_5
    ATTR_TABLE:
      RENAME_SET_VALUE pourcentage > note = @Value(note)/100
      SET_TO diff
      REMOVE _clipped
      REMOVE status
      REMOVE addresses{}
      REMOVE rnb_id.total_count
      REMOVE id.total_count
      REMOVE area_rnb
      REMOVE area_rnb_recouv
    -> FeatureJoiner_2 [RIGHT]

Bookmark: 1 OSM pour X RNB
Tester_7
    BOOL_OP = OR
    TEST_CLAUSE = TEST @Value(rnb_id.total_count) = 1
    TEST_MODE = TEST
    PASSED -> AttributeKeeper_3
AttributeKeeper_3
    CREATE_BULK_MODE_FEATURES = NO
    KEEP_ATTRS = id,pourcentage,rnb_id
    -> ListBuilder
ListBuilder
    GROUP_BY = id
    LIST_ATTRS_TO_INCLUDE = pourcentage rnb_id
    LIST_NAME = _list
    -> ListElementCounter
ListElementCounter
    CNT_ATTR = _element_count
    LIST_NAME = _list{}
    -> ListSummer
ListSummer
    RESULT = somme
    SRC_LIST = _list{}.pourcentage
    -> ListConcatenator
ListConcatenator
    DROP_EMPTY_PARTS = No
    LIST_ATTR = _list{}.rnb_id
    SEP = ;
    VAL_ATTR = rnb_id
    -> AttributeCreator
AttributeCreator
    ATTR_TABLE = SET_TO note = @round(@div(@Value(somme),@Value(_element_count)),0)
    -> AttributeManager_6
AttributeManager_6
    ATTR_TABLE:
      SET_TO diff = multiple
      REMOVE _list{}.pourcentage
      REMOVE _list{}.rnb_id
      REMOVE _element_count
      SET_TO note = @Value(note)/100
      REMOVE somme
    -> FeatureJoiner [LEFT]

Bookmark: Onreconstruit la donnée OSM - RNB
FeatureJoiner
    ATTR_CONFLICT_RES = Prefer Left
    GEOMETRY_HANDLING = Prefer Right
    JOIN_KEYS = id id AUTO
    JOIN_MODE = Inner
    JOINED -> AttributeKeeper_2
AttributeKeeper_2
    CREATE_BULK_MODE_FEATURES = NO
    KEEP_ATTRS = id,note,rnb_id,diff
    -> DuplicateFilter
DuplicateFilter
    INPUT_ORDERED_CHOICE = No
    KEYATTR = id rnb_id
    UNIQUE -> Correspondance OSM - RNB (writer GEOJSON_4)
